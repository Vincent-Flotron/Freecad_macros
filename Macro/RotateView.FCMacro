from PySide2 import QtCore, QtWidgets
import sys
mod_to_import = 'MyTools'
if mod_to_import in sys.modules:
    del sys.modules[mod_to_import]
import MyTools


# Class to create a simple GUI for selecting the view and applying rotation
class ViewSelectionDialog(QtWidgets.QDialog):
    def __init__(self, parent=None):
        super(ViewSelectionDialog, self).__init__(parent)
        
        # Set window title
        self.setWindowTitle("Select Projection View")
        
        # Define the available views
        self.views = ['FrontBottomLeft', 'FrontBottomRight', 'FrontTopRight', 'FrontTopLeft']
        
        # Create the combo box for view selection
        self.combo = QtWidgets.QComboBox()
        self.combo.addItems(self.views)
        
        # Create a Finish button
        self.finish_button = QtWidgets.QPushButton("Finish")
        
        # Create layout and add widgets
        layout = QtWidgets.QVBoxLayout()
        layout.addWidget(QtWidgets.QLabel("Select a view:"))
        layout.addWidget(self.combo)
        layout.addWidget(self.finish_button)
        self.setLayout(layout)
        
        # Connect signals to methods
        self.combo.currentIndexChanged.connect(self.update_view)
        self.finish_button.clicked.connect(self.accept)
        
        # Connect ENTER key to the finish action
        self.combo.installEventFilter(self)
        
        # Call rotate_projgroup with the default view on startup
        self.update_view()
    
    def update_view(self):
        """Update the view when a new one is selected."""
        selected_view = self.combo.currentText()
        MyTools.rotate_projgroup(view=selected_view)
    
    def eventFilter(self, source, event):
        """Capture the ENTER key to finish selection."""
        if event.type() == QtCore.QEvent.KeyPress:
            if event.key() == QtCore.Qt.Key_Return or event.key() == QtCore.Qt.Key_Enter:
                self.accept()
                return True
        return super(ViewSelectionDialog, self).eventFilter(source, event)

# Function to show the view selection dialog
def select_view_dialog():
    dialog = ViewSelectionDialog()
    dialog.exec_()

# Example usage:
# Call this to open the view selection GUI
select_view_dialog()
