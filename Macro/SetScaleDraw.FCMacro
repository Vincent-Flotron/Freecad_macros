# -*- coding: utf-8 -*-

# Macro Begin: /home/spot/.local/share/FreeCAD/Macro/SetScaleDraw.FCMacro +++++++++++++++++++++++++++++++++++++++++++++++++
import FreeCADGui as     Gui
import sys
mod_to_import = 'MyTools'
if mod_to_import in sys.modules:
    del sys.modules[mod_to_import]
import MyTools

# Get the selected object
selected_obj = Gui.Selection.getSelection()

if MyTools.is_DrawProjGroup(selected_obj):
    page  = MyTools.get_Page_of_DrawProjGroup(selected_obj)
    group = selected_obj
else:
    page       = MyTools.get_page_of_DrawProjGroupItem(          selected_obj )
    group      = MyTools.get_DrawProjGroup_of_DrawProjGroupItem( selected_obj )

print(f"group: {group}")

MyTools.set_draw_cartridge_scale(page, group)


# Macro End: /home/spot/.local/share/FreeCAD/Macro/SetScaleDraw.FCMacro +++++++++++++++++++++++++++++++++++++++++++++++++
