import FreeCAD
import TechDrawGui
import FreeCADGui
import os
import subprocess
from PyPDF2 import PdfMerger
from PySide import QtGui, QtWidgets

# Get the active document and the selection
doc = FreeCAD.ActiveDocument
selection = FreeCADGui.Selection.getSelection()

# Get the directory of the current macro
macro_directory = os.path.dirname(os.path.abspath(__file__))

# Initialize PdfMerger
merger = PdfMerger()

# Ask user for the folder to save the PDFs
folder_dialog = QtGui.QFileDialog()
folder_dialog.setFileMode(QtGui.QFileDialog.Directory)
folder_dialog.setOption(QtGui.QFileDialog.ShowDirsOnly)

# If user selects a folder, proceed with PDF export
if folder_dialog.exec_():
    root = folder_dialog.selectedFiles()[0] + "/"
    
    # Ask for the name of the output PDF file
    output_pdf_name, ok = QtWidgets.QInputDialog.getText(
        None, "Output PDF Name", "Enter the name for the output PDF (without extension):", QtWidgets.QLineEdit.Normal, "selected_pages_output"
    )
    
    if ok and output_pdf_name:
        output_pdf = os.path.join(root, f"{output_pdf_name}.pdf")
        
        # List to store PDF file paths for deletion later
        pdf_files = []

        for obj in selection:
            # Check if the object is a TechDraw page
            if obj.TypeId == "TechDraw::DrawPage":
                filename = f"{root}{obj.Name}.pdf"
                
                # Check if the file exists and delete it
                if os.path.exists(filename):
                    os.remove(filename)
                
                # Export the TechDraw page as PDF
                TechDrawGui.exportPageAsPdf(obj, filename)
                
                # Add the pdf to the merger and keep track of the filename
                merger.append(filename)
                pdf_files.append(filename)

        # Write the output PDF if there are pages
        if merger.pages:
            merger.write(output_pdf)
            merger.close()

            # Delete the individual PDF files after merging
            for pdf_file in pdf_files:
                if os.path.exists(pdf_file):
                    os.remove(pdf_file)

            # Ask for opening the file
            msg_box = QtGui.QMessageBox()
            msg_box.setIcon(QtGui.QMessageBox.Information)
            msg_box.setText(f"Selected pages exported to '{output_pdf}'")
            msg_box.setWindowTitle("Export Complete")

            ok_button = msg_box.addButton("OK", QtGui.QMessageBox.AcceptRole)
            open_explorer_button = msg_box.addButton("Open In File Explorer", QtGui.QMessageBox.ActionRole)

            msg_box.exec_()

            if msg_box.clickedButton() == open_explorer_button:
                try:
                    if os.name == 'nt':  # For Windows
                        os.startfile(os.path.dirname(output_pdf))
                    elif os.name == 'posix':  # For macOS and Linux
                        opener = 'open' if sys.platform == 'darwin' else 'xdg-open'
                        subprocess.call([opener, os.path.dirname(output_pdf)])
                except Exception as e:
                    QtGui.QMessageBox.warning(None, "Error", f"Failed to open file explorer: {str(e)}")


            # Open the final PDF with the default system PDF software
            try:
                if os.name == 'nt':  # For Windows
                    os.startfile(output_pdf)
                elif os.name == 'posix':  # For macOS and Linux
                    opener = 'open' if sys.platform == 'darwin' else 'xdg-open'
                    subprocess.call([opener, output_pdf])
            except Exception as e:
                QtGui.QMessageBox.warning(None, "Error", f"Failed to open the PDF: {str(e)}")
        else:
            QtGui.QMessageBox.warning(None, "No Pages Selected", "No TechDraw pages were selected for export.")
    else:
        QtGui.QMessageBox.warning(None, "Invalid Name", "No valid name was provided for the output PDF.")
