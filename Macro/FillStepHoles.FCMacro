# -*- coding: utf-8 -*-

# Macro Begin: /home/wace/snap/freecad/common/FreeCAD/Macro/FillStepHoles.FCMacro +++++++++++++++++++++++++++++++++++++++++++++++++
import FreeCAD
import PartDesign
import PartDesignGui
import Sketcher

# Gui.runCommand('Std_DlgMacroRecord',0)
# Gui.ActiveDocument.ActiveView.setActiveObject('pdbody',App.getDocument(document).getObject(body))
# Gui.Selection.clearSelection()
# Gui.Selection.addSelection(document,body,'Pocket010.Sketch066.')
# Gui.runCommand('Std_ToggleVisibility',0)
# Gui.Selection.clearSelection()
# Gui.Selection.addSelection(document,body,'Pocket022.Sketch078.')
# Gui.runCommand('Std_ToggleVisibility',0)
# Gui.Selection.clearSelection()
# Gui.Selection.addSelection(document,body,'Pocket022.')
# Gui.Selection.clearSelection()
# Gui.Selection.addSelection(document,body,'Pocket022.Face3',3660.08,-1843,856.74)
### Begin command PartDesign_NewSketch
support_map_mode = 'FlatFace'
sketch_type      = 'Sketcher::SketchObject'

document         = 'Maison2'

body             = 'Body006'
new_sketch       = 'Sketch268'
support_func     = 'Pocket022'
support_face     = 'Face3'

App.getDocument(document).getObject(body).newObject(sketch_type,new_sketch)
App.getDocument(document).getObject(new_sketch).Support = (App.getDocument(document).getObject(support_func),[support_face,])
App.getDocument(document).getObject(new_sketch).MapMode = support_map_mode
App.ActiveDocument.recompute()
# Gui.getDocument(document).setEdit(App.getDocument(document).getObject(body), 0, 'Sketch268.')
# ActiveSketch = App.getDocument(document).getObject(new_sketch)
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument(document).getObject(body), 'Sketch268.'))
# if ActiveSketch.ViewObject.ShowSupport:
#   tv.show([ref[0] for ref in ActiveSketch.Support if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument(document).getObject(new_sketch)
# if ActiveSketch.ViewObject.RestoreCamera:
#   ActiveSketch.ViewObject.TempoVis.saveCamera()
#   if ActiveSketch.ViewObject.ForceOrtho:
#     ActiveSketch.ViewObject.Document.ActiveView.setCameraType('Orthographic')
# 
### End command PartDesign_NewSketch




# Gui.Selection.clearSelection()
# Gui.Selection.addSelection(document,body,'Pocket022.')
# Gui.runCommand('Std_ToggleVisibility',0)
# Gui.Selection.clearSelection()
# Gui.runCommand('Sketcher_External',0)
# Gui.Selection.addSelection(document,body,'Sketch066.Edge1',3843.02,-1843,862.904)
App.getDocument(document).getObject(new_sketch).addExternal("Sketch066","Edge1")
# Gui.Selection.clearSelection()
# Gui.Selection.addSelection(document,body,'Sketch066.Edge2',3551.96,-1843,864.092)
App.getDocument(document).getObject(new_sketch).addExternal("Sketch066","Edge2")
# Gui.Selection.clearSelection()
# Gui.runCommand('Sketcher_CompCreateCircle',0)
App.getDocument(document).getObject(new_sketch).addGeometry(Part.Circle(App.Vector(3847.000000,-25.000000,0),App.Vector(0,0,1),40.700249),False)
App.getDocument(document).getObject(new_sketch).addConstraint(Sketcher.Constraint('Coincident',0,3,-3,3)) 
App.getDocument(document).getObject(new_sketch).addGeometry(Part.Circle(App.Vector(3552.801639,-25.000000,0),App.Vector(0,0,1),52.235826),False)
App.getDocument(document).getObject(new_sketch).addConstraint(Sketcher.Constraint('Coincident',1,3,-4,3)) 
# Gui.Selection.addSelection(document,body,'Sketch268.ExternalEdge1',3853.13,-1843.01,853.771,False)
# Gui.Selection.addSelection(document,body,'Sketch268.Edge1',3834.42,-1843.01,818.435,False)
# Gui.Selection.addSelection(document,body,'Sketch268.Edge2',3595.06,-1843.01,826.439,False)
### Begin command Sketcher_ConstrainEqual
App.getDocument(document).getObject(new_sketch).addConstraint(Sketcher.Constraint('Equal',-3,0))
App.getDocument(document).getObject(new_sketch).addConstraint(Sketcher.Constraint('Equal',0,1))
### End command Sketcher_ConstrainEqual
# Gui.Selection.clearSelection()
App.ActiveDocument.recompute()
# Gui.Selection.addSelection(document,body,'Sketch268.')
# ActiveSketch = App.getDocument(document).getObject(new_sketch)
# tv = ActiveSketch.ViewObject.TempoVis
# if tv:
#   tv.restore()
# ActiveSketch.ViewObject.TempoVis = None
# del(tv)
# del(ActiveSketch)
# 
### Begin command PartDesign_Pad
App.getDocument(document).getObject(body).newObject('PartDesign::Pad','Pad137')
App.getDocument(document).getObject('Pad137').Profile = App.getDocument(document).getObject(new_sketch)
App.getDocument(document).getObject('Pad137').Length = 10
App.ActiveDocument.recompute()
App.getDocument(document).getObject('Pad137').ReferenceAxis = (App.getDocument(document).getObject(new_sketch),['N_Axis'])
App.getDocument(document).getObject(new_sketch).Visibility = False
App.ActiveDocument.recompute()
# App.getDocument(document).getObject('Pad137').ViewObject.ShapeColor=getattr(App.getDocument(document).getObject(support_func).getLinkedObject(True).ViewObject,'ShapeColor',App.getDocument(document).getObject('Pad137').ViewObject.ShapeColor)
# App.getDocument(document).getObject('Pad137').ViewObject.LineColor=getattr(App.getDocument(document).getObject(support_func).getLinkedObject(True).ViewObject,'LineColor',App.getDocument(document).getObject('Pad137').ViewObject.LineColor)
# App.getDocument(document).getObject('Pad137').ViewObject.PointColor=getattr(App.getDocument(document).getObject(support_func).getLinkedObject(True).ViewObject,'PointColor',App.getDocument(document).getObject('Pad137').ViewObject.PointColor)
# App.getDocument(document).getObject('Pad137').ViewObject.Transparency=getattr(App.getDocument(document).getObject(support_func).getLinkedObject(True).ViewObject,'Transparency',App.getDocument(document).getObject('Pad137').ViewObject.Transparency)
# App.getDocument(document).getObject('Pad137').ViewObject.DisplayMode=getattr(App.getDocument(document).getObject(support_func).getLinkedObject(True).ViewObject,'DisplayMode',App.getDocument(document).getObject('Pad137').ViewObject.DisplayMode)
# Gui.getDocument(document).setEdit(App.getDocument(document).getObject(body), 0, 'Pad137.')
# Gui.Selection.clearSelection()
### End command PartDesign_Pad
# Gui.Selection.clearSelection()
# Gui.Selection.addSelection(document,body,'Pocket022.')
# Gui.runCommand('Std_ToggleVisibility',0)
App.getDocument(document).getObject('Pad137').UseCustomVector = 0
App.getDocument(document).getObject('Pad137').Direction = (0, -1, 0)
App.getDocument(document).getObject('Pad137').ReferenceAxis = (App.getDocument(document).getObject(new_sketch), ['N_Axis'])
App.getDocument(document).getObject('Pad137').AlongSketchNormal = 1
App.getDocument(document).getObject('Pad137').Type = 2
App.getDocument(document).getObject('Pad137').UpToFace = None
App.getDocument(document).getObject('Pad137').Reversed = 1
App.getDocument(document).getObject('Pad137').Midplane = 0
App.getDocument(document).getObject('Pad137').Offset = 0
App.getDocument(document).recompute()
App.getDocument(document).getObject(support_func).Visibility = False
# Gui.getDocument(document).resetEdit()
App.getDocument(document).getObject(new_sketch).Visibility = False
# Gui.Selection.clearSelection()
# Gui.Selection.addSelection(document,body,'Pad137.')
# Gui.runCommand('Std_ToggleVisibility',0)
FreeCAD.getDocument(document).getObject('Pad137').Refine = True

# Macro End: /home/wace/snap/freecad/common/FreeCAD/Macro/FillStepHoles.FCMacro +++++++++++++++++++++++++++++++++++++++++++++++++
