# -*- coding: utf-8 -*-

# Macro Begin: /home/spot/.local/share/FreeCAD/Macro/newTechDraw_std.FCMacro +++++++++++++++++++++++++++++++++++++++++++++++++
import FreeCAD  as App
# import TechDraw
import sys
mod_to_import = 'MyTools'
if mod_to_import in sys.modules:
    del sys.modules[mod_to_import]
import MyTools


MyTools.new_techdraw_page()
# Macro End: /home/spot/.local/share/FreeCAD/Macro/newTechDraw_std.FCMacro +++++++++++++++++++++++++++++++++++++++++++++++++
