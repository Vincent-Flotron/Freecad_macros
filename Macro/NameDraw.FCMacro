# -*- coding: utf-8 -*-

# Macro Begin: /home/spot/.local/share/FreeCAD/Macro/NameDraw.FCMacro +++++++++++++++++++++++++++++++++++++++++++++++++

import FreeCADGui as     Gui
import sys
mod_to_import = 'MyTools'
if mod_to_import in sys.modules:
    del sys.modules[mod_to_import]
import MyTools

# Get the selected object
selected_objs = Gui.Selection.getSelection()
page          = MyTools.get_page_of_DrawProjGroupItem(     selected_objs )
print(f"page: {page.Name}")
part_name     = MyTools.get_partname_of_DrawProjGroupItem( selected_objs )
print(f"part_name: {part_name}")

# Name the draw using the name of the first related part
MyTools.name_draw(page, selected_objs)

# Macro End: /home/spot/.local/share/FreeCAD/Macro/NameDraw.FCMacro +++++++++++++++++++++++++++++++++++++++++++++++++
