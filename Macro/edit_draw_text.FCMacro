# Ensure that a TechDraw::DrawPage is selected
selected_obj = App.Gui.Selection.getSelection()[0] if App.Gui.Selection.getSelection() else None

if selected_obj and selected_obj.TypeId == 'TechDraw::DrawPage':
    # Access the template associated with the selected page
    template = selected_obj.Template

    if template:
        # Access the editable text fields of the template
        editable_texts = template.EditableTexts
        
        # Check if "Subtitle" exists in the editable fields
        if "Subtitle" in editable_texts:
            # Update the "Subtitle" field value
            editable_texts["Subtitle"] = "New Subtitle ValueV2"
            template.EditableTexts = editable_texts
            
            # Recompute the document to apply changes
            App.activeDocument().recompute()
        else:
            print("Subtitle field not found in the template.")
    else:
        print("No template assigned to the selected page.")
else:
    print("Please select a valid TechDraw::DrawPage.")
