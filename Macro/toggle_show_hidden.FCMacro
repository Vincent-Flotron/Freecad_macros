# -*- coding: utf-8 -*-
from PySide import QtGui
import sys
mod_to_import = 'MyTools'
if mod_to_import in sys.modules:
    del sys.modules[mod_to_import]
import MyTools


def toggle_show_hidden():
    # Get the selected object
    selection = FreeCADGui.Selection.getSelection()
    
    if not selection:
        QtGui.QMessageBox.warning(None, "Warning", "No object selected.")
        return
    
    for sel in selection:
        sel.HardHidden = not sel.HardHidden

    FreeCAD.ActiveDocument.recompute()
    

if __name__ == "__main__":
    # Run the function
    toggle_show_hidden()
