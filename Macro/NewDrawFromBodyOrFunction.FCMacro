# -*- coding: utf-8 -*-

# Macro Begin: /home/spot/.local/share/FreeCAD/Macro/NewDrawFromBodyOrFunction.FCMacro +++++++++++++++++++++++++++++++++++++++++++++++++
# import FreeCADGui as Gui
# import FreeCAD    as App
import sys
mod_to_import = 'MyTools'
if mod_to_import in sys.modules:
    del sys.modules[mod_to_import]
import MyTools
from MyTools import Display


# Select only Body
def select_body_parent_if_exist(selected_objects):
    sel_objs    = []
    body_parent = None
    for sel_obj in selected_objects:
        if sel_obj.TypeId != 'TechDraw::Body':
            body_parent = MyTools.find_body_parent(sel_obj)
            body_parent = body_parent if body_parent else sel_obj
        else:
            body_parent = sel_obj
        sel_objs.append(body_parent)
    return sel_objs


# Get the list of selected objects
selected_objects = Gui.Selection.getSelection()


# Check if Ctrl key is pressed
if MyTools.is_ctrl_pressed():
    dialog = MyTools.TechDrawSelector(Gui.getMainWindow())
    dialog.exec_()

    # Get the selected item name after dialog closes
    page = MyTools.Page(dialog.get_next_name(), dialog.get_next_number())
    # Display.show_message(f"__new page_number {page.get_number_str()}")
    # Display.show_message(f"__new page_name {page.get_name()}")
else:
    page = None

# Make new draw
doc, new_page = MyTools.new_techdraw_page(page=page)

if not doc == None and not new_page == None:
    # Add ProjGroup to the created page
    last_ProjGroup     = MyTools.get_highest_ProjGroup_number(doc)
    new_ProjGroup_numb = last_ProjGroup + 1
    new_ProjGroup_name = f"ProjGroup{new_ProjGroup_numb:03}"
    new_ProjGroup      = doc.addObject('TechDraw::DrawProjGroup',new_ProjGroup_name)


    # Select only Bodies
    selected_objects     = select_body_parent_if_exist(selected_objects)
    new_ProjGroup.Source = selected_objects

    # Add third view
    new_ProjGroup_third_numb   = last_ProjGroup + 2
    new_ProjGroup_third_name   = f"ProjGroup{new_ProjGroup_third_numb:03}"
    new_ProjGroup_third        = doc.addObject('TechDraw::DrawProjGroup',new_ProjGroup_third_name)
    new_ProjGroup_third.Source = selected_objects

    # Set the scales
    new_scale, scale_type                 = MyTools.get_prefered_scale_deci_and_type("techdraw_prefered_scale")
    new_scale_third, new_scale_type_third = MyTools.get_prefered_scale_deci_and_type("techdraw_prefered_scale_third_view")

    # Add ProjGroups
    new_page.addView(new_ProjGroup)
    new_page.addView(new_ProjGroup_third)

    # Update scales
    new_ProjGroup.ScaleType       = scale_type
    new_ProjGroup.Scale           = new_scale       if new_scale       else new_ProjGroup.Scale
    new_ProjGroup_third.ScaleType = new_scale_type_third
    new_ProjGroup_third.Scale     = new_scale_third if new_scale_third else new_ProjGroup_third.Scale

    # Add first projections
    new_ProjGroup.addProjection('Front')
    new_ProjGroup.Anchor.Direction = App.Vector(0.000,0.000,1.000)
    new_ProjGroup.Anchor.RotationVector = App.Vector(1.000,1.000,1.000)
    new_ProjGroup.Anchor.XDirection = App.Vector(1.000,0.000,0.000)
    new_page.ViewObject.doubleClicked()
    new_ProjGroup.X = new_page.Template.Width  / 2
    new_ProjGroup.Y = new_page.Template.Height / 2
    new_ProjGroup.Anchor.recompute()
    # third view
    new_ProjGroup_third.addProjection('Front')
    MyTools.rotate_projgroup([new_ProjGroup_third])
    new_ProjGroup_third.Anchor.recompute()

    doc.recompute()



    # Add extra projections to ProjGroup
    new_ProjGroup.addProjection('Left')
    # new_ProjGroup.addProjection('FrontBottomLeft')
    # new_ProjGroup.addProjection('Bottom')
    # new_ProjGroup.addProjection('FrontBottomRight')
    # new_ProjGroup.addProjection('Right')
    # new_ProjGroup.addProjection('FrontTopRight')
    new_ProjGroup.addProjection('Top')
    # new_ProjGroup.addProjection('FrontTopLeft')

    # # Update scales
    # new_ProjGroup.ScaleType       = scale_type
    # new_ProjGroup.Scale           = new_scale       if new_scale       else new_ProjGroup.Scale
    # new_ProjGroup_third.ScaleType = new_scale_type_third
    # new_ProjGroup_third.Scale     = new_scale_third if new_scale_third else new_ProjGroup_third.Scale

    Gui.ActiveDocument.resetEdit()


    # Name the draw
    MyTools.name_draw(new_page, [new_ProjGroup.Views[0]])

    # Set cartridge's scale
    MyTools.set_draw_cartridge_scale(new_page, new_ProjGroup)


# Macro End: /home/spot/.local/share/FreeCAD/Macro/NewDrawFromBodyOrFunction.FCMacro +++++++++++++++++++++++++++++++++++++++++++++++++
