# -*- coding: utf-8 -*-

# Macro Begin: /home/spot/.local/share/FreeCAD/Macro/LockPos.FCMacro +++++++++++++++++++++++++++++++++++++++++++++++++
import FreeCADGui as Gui
import sys
mod_to_import = 'MyTools'
if mod_to_import in sys.modules:
    del sys.modules[mod_to_import]
import MyTools

# Get the list of selected objects
selected_objects = Gui.Selection.getSelection()
MyTools.lock_objects(selected_objects)


# Macro End: /home/spot/.local/share/FreeCAD/Macro/LockPos.FCMacro +++++++++++++++++++++++++++++++++++++++++++++++++
