import sys
if 'DisplayAttributes_module' in sys.modules:
    del sys.modules['DisplayAttributes_module']
import DisplayAttributes_module as dam


if __name__ == "__main__":
    dam.display_attributes()
