import FreeCAD as App
import FreeCADGui as Gui
import numpy as np

def create_transformation_matrix(proj_xdir, proj_ydir, proj_dir):
    """
    Create a transformation matrix to project 3D points onto the 2D plane defined by proj_xdir and proj_ydir.
    """
    # Construct a 3x3 matrix with the directions as columns
    # transformation_matrix = np.array([
    #     [proj_xdir.x, proj_xdir.y, proj_xdir.z],
    #     [proj_ydir.x, proj_ydir.y, proj_ydir.z],
    #     [proj_dir.x, proj_dir.y, proj_dir.z]
    # ])
    transformation_matrix = np.array([
        [proj_xdir.x, proj_xdir.y, proj_xdir.z],
        [proj_ydir.x, proj_ydir.y, proj_ydir.z],
        [proj_dir.x,  proj_dir.y,  proj_dir.z]
    ])
    return transformation_matrix

def project_to_2d(point, transformation_matrix):
    """
    Project a 3D point to 2D space using the given transformation matrix.
    """
    transformed_point = transformation_matrix @ np.array([point.x, point.y, point.z])
    return App.Vector(transformed_point[0], transformed_point[1], 0)

def get_projgroup_dimensions_from_boundingbox(proj_group):
    x_min, y_min = float('inf'), float('inf')
    x_max, y_max = float('-inf'), float('-inf')

    # Iterate over the views in the projection group
    print(f'proj_group.Views: {proj_group.Views}')
    for view_item in proj_group.Views:
        try:
            print(f'view_item.TypeId: {view_item.TypeId}')
            print(f'view_item.Name: {view_item.Name}')
            print(f'view_item: {view_item}')
            
            # Get the source object of the projection
            source_object = view_item.Source[0]

            # Check if the source object has a ViewObject with a getBoundingBox method
            if hasattr(source_object, "ViewObject"):
                bbox = source_object.ViewObject.getBoundingBox()

                # Extract the bounding box corners
                points = [
                    App.Vector(bbox.XMin, bbox.YMin, bbox.ZMin),
                    App.Vector(bbox.XMin, bbox.YMax, bbox.ZMin),
                    App.Vector(bbox.XMax, bbox.YMin, bbox.ZMin),
                    App.Vector(bbox.XMax, bbox.YMax, bbox.ZMin),
                    App.Vector(bbox.XMin, bbox.YMin, bbox.ZMax),
                    App.Vector(bbox.XMin, bbox.YMax, bbox.ZMax),
                    App.Vector(bbox.XMax, bbox.YMin, bbox.ZMax),
                    App.Vector(bbox.XMax, bbox.YMax, bbox.ZMax)
                ]

                # Get the projection direction and x direction
                proj_dir = view_item.Direction
                proj_xdir = view_item.XDirection
                proj_ydir = proj_dir.cross(proj_xdir).normalize()

                # Create transformation matrix
                transformation_matrix = create_transformation_matrix(proj_xdir, proj_ydir, proj_dir)

                # Project the bounding box points to 2D
                transformed_points = [project_to_2d(p, transformation_matrix) for p in points]

                # Find the extents in the 2D projected space
                for p in transformed_points:
                    x_min = min(x_min, p.x)
                    x_max = max(x_max, p.x)
                    y_min = min(y_min, p.y)
                    y_max = max(y_max, p.y)
            else:
                print(f"Skipping item: {view_item.Name}, missing ViewObject or bounding box properties.")
        
        except AttributeError:
            print(f"Skipping item: {view_item.Name}, missing source properties.")
    
    # Check if valid bounding box was found
    if x_min == float('inf') or y_min == float('inf'):
        print("No valid source objects found with bounding box properties.")
        return None, None

    # Calculate width and height from bounding box in projected space
    width = (x_max - x_min) * proj_group.Scale
    height = (y_max - y_min) * proj_group.Scale
    
    return width, height

# Example usage
doc = App.ActiveDocument

proj_group = Gui.Selection.getSelection()[0]

if proj_group and proj_group.TypeId == 'TechDraw::DrawProjGroup':
    width, height = get_projgroup_dimensions_from_boundingbox(proj_group)
    if width is not None and height is not None:
        print(f"Projection Group Width: {width}")
        print(f"Projection Group Height: {height}")
    else:
        print("Could not compute dimensions. Check for valid views in the group.")
else:
    print("Selected object is not a TechDraw::DrawProjGroup")
